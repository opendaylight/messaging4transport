module messaging4transport {
    yang-version 1;
    namespace "urn:opendaylight:params:xml:ns:yang:messaging4transport";
    prefix "messaging4transport";

    revision "2015-01-05" {
        description "Initial revision of messaging4transport model";
    }

    container amqp-user-agents {
        list amqp-user-agent {
            key "agent-id";

            leaf agent-id {
	            type string;
            }

            leaf host {
                type string;
            }

            leaf port {
                type int32;
            }

            leaf username {
                type string;
            }

            leaf password {
                type string;
            }

            list receiver {
                key message-id;
                leaf message-id {
                    type string;
                }
            }
        }
    }
}
