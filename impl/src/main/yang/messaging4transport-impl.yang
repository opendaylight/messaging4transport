module messaging4transport-impl {
    yang-version 1;
    namespace "urn:opendaylight:params:xml:ns:yang:messaging4transport:impl";
    prefix "messaging4transport-impl";

    import config { prefix config; revision-date 2013-04-05; }
    import opendaylight-md-sal-dom {prefix dom; revision-date 2013-10-28;}

    description
        "Service definition for Messaging4Transport project";

    revision "2014-12-10" {
        description
            "Initial revision";
    }

    identity messaging-transport {
        base "config:service-type";
        config:java-class "org.opendaylight.messaging4transport.api.Messaging4Transport";
    }

    identity messaging4transport {
        base config:module-type;
        config:provided-service messaging-transport;
        config:java-name-prefix Messaging4Transport;
    }

    augment "/config:modules/config:module/config:configuration" {
        case messaging4transport {
            when "/config:modules/config:module/config:type = 'messaging4transport'";
            container dom-broker {
                uses config:service-ref {
                    refine type {
                        mandatory true;
                        config:required-identity dom:dom-broker-osgi-registry;
                    }
                }
            }
        }
    }
}
